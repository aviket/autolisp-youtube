(defun remove-nil-sq (lst)
  (setq lst1 (vl-remove-if 'null lst))
  (mapcar '(lambda (x) (* x x )) lst1) 
)
(defun princpi ()
    (princ pi)
)
(defun c:princpi ()
     (princ pi)
)
(setq trialstring "This is a trial string")
(setq trialint -99)
(setq trialreal -99.99)
(setq triallist (list 1 2 3 4 "abc" 5 6 (list 7 8 9)))
